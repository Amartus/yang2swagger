module list-manager {
    namespace "urn:demo:list-manager";
    prefix "lm";
    yang-version 1.1;
    import ietf-yang-types {prefix yang;}
    import ietf-yang-schema-mount { prefix "yangmnt"; }

    revision "2022-03-12" {
        description "First cut";
    }
    typedef list-entry-status {
        type enumeration {
            enum active;
            enum disabled;
        }
    }
    grouping list-config-parameters {
        leaf name {
            type string;
        }
        leaf status {
            type list-entry-status;
        }
    }
    grouping list-state-attributes {
        leaf in-use {
            config false;
            type boolean;
        }
        leaf created-at {
            config false;
            type yang:date-and-time;
        }
    }
    list list-entry {
        key name;
        uses list-config-parameters;
        uses list-state-attributes;
        leaf entry-type {
            type string;
        }
        container specific-config {
            yangmnt:mount-point entry-type-specific-data;
        }
        action list-entry-action {
            input {
                leaf entry-action-input {
                    type string;
                }
            }
            output {
                leaf entry-action-output {
                    type string;
                }
            }
        }
    }
    rpc list-manager-operation {
        input {
            leaf rpc-operation-input {
                type string;
            }
        }
        output {
            leaf rpc-operation-output {
                type string;
            }
        }
    }
}
