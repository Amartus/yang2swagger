module rpc-augmentations {
    namespace "http://amartus/ns/yang/rpc-augmentations";
    prefix raug;
    import rpc-basic { prefix rb; }

    grouping addition {
        container a-container {
            leaf abcd { type string; }
        }
    }


    grouping aug1 {
        leaf leaf11 {type string;}
        leaf leaf12 {type string;}
        leaf leaf13 {type string;}
    }

    grouping aug2 {
        container con2 {
            leaf leaf21 { type string; }
        }
        list list2 {
           uses aug1;
           key 'leaf11';
        }
    }

    augment "/rb:with-multiple-elements/rb:input" {
        uses aug1;
    }

    augment "/rb:with-multiple-elements/rb:input" {
        uses aug2;
    }

    augment "/rb:root/rb:c-res" {
        uses addition;
    }

    augment "/rb:rock-the-house/rb:input/rb:xyz/rb:c-res" {
        uses addition;
    }

    augment "/rb:rock-the-house/rb:output/rb:response" {
        uses addition;
    }

    augment "aug-root/a" {
        container ab {
            uses addition;
        }
    }

    container aug-root {
        list a {
            leaf key {type string; }

        }
        container b {
            uses addition;
        }
    }
}
