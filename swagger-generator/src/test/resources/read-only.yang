module read-only {
  namespace "http://amartus/ns/yang/simplests";
  prefix ro;
  organization "test-yang";
  description "read-only test module";

  revision 2016-06-22 {
      description "Final";
  }

  typedef myint1 {
    type int32 {
        range 1..3;
    }
  }

  container simple-root {
    list c1 {
        leaf id {
            type myint1;
        }

        list c2 {
                leaf id {
                    type int32;
                }
                config false;
                key "id";

                container c3 {
                    container c4 {
                        leaf someValue {
                            type string;
                        }
                        list c5 {
                                leaf id {
                                    type myint1;
                                }
                                key "id";
                        }
                    }
                }
            }
        key "id";
    }
  }

  // config-true container with mixed children - exercises split config/state (issue #74)
  container mixed {
    description "container holding both config and state data";
    leaf cfg {
      type string;
    }
    leaf state {
      type string;
      config false;
    }
    container statistics {
      config false;
      leaf counter {
        type int32;
      }
    }
  }

}
