module simpleAugmentation {
  namespace "http://amartus/ns/yang/simpleAugmentation";
  prefix a;

  import simplest {
    prefix s;
  }

  organization "test-yang";
  description "simple augmentation";

  augment "/s:simple-root/s:children1/" {
    leaf-list added-list {
        type string;
    }
  }

  augment "/s:simple-root/" {
      when "s:children1/s:id = '1'";
      container added-a {
          config false;
          leaf a1 {
            type leafref {
                path "../id";
            }
          }
          leaf a2 { type int32; }
          leaf-list a3 { type int64;}
          container children1 {
            leaf a1 { type string; }
          }
      }
    }

}
