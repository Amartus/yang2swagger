module TapiTopology {
    namespace "urn:onf:params:xml:ns:yang:TapiTopology";
    prefix TapiTopology;
    import Tapi {
        prefix Tapi;
    }
    organization "ONF (Open Networking Foundation) IMP Working Group";
    contact "WG Web: <https://www.opennetworking.org/technical-communities/areas/services/>
        WG List: <mailto: <wg list name>@opennetworking.org>
        WG Chair: your-WG-chair
                <mailto:your-WG-chair@example.com>
        Editor: your-name
                <mailto:your-email@example.com>";
    description "none";
    revision 2016-06-29 {
        description "Latest revision";
        reference "RFC 6020 and RFC 6087";
    }
    
    augment "/Tapi:Context/Tapi:_topology" {
        uses Topology;
    }
    
    /***********************
    * package ObjectClasses
    **********************/ 
        grouping Link {
            list _linkPort {
                key 'localId';
                config false;
                min-elements 2;
                uses LinkPort;
                description "none";
            }
            leaf-list _node {
                type leafref {
                    path '/Tapi:Context/Tapi:_topology/_node/uuid';
                }
                config false;
                min-elements 2;
                description "none";
            }
            container _state {
                config false;
                uses Tapi:AdminStatePac;
                description "none";
            }
            container _transferCapacity {
                config false;
                uses TransferCapacityPac;
                description "none";
            }
            container _transferCost {
                config false;
                uses TransferCostPac;
                description "none";
            }
            container _transferIntegrity {
                config false;
                uses TransferIntegrityPac;
                description "none";
            }
            container _transferTiming {
                config false;
                uses TransferTimingPac;
                description "none";
            }
            container _riskParameter {
                config false;
                uses RiskParameterPac;
                description "none";
            }
            container _validation {
                config false;
                uses ValidationPac;
                description "none";
            }
            container _lpTransition {
                config false;
                uses LayerProtocolTransitionPac;
                description "none";
            }
            leaf-list layerProtocolName {
                type Tapi:LayerProtocolName;
                config false;
                min-elements 1;
                description "none";
            }
            leaf direction {
                type Tapi:ForwardingDirection;
                config false;
                description "The directionality of the Link. 
                    Is applicable to simple Links where all LinkEnds are BIDIRECTIONAL (the Link will be BIDIRECTIONAL) or UNIDIRECTIONAL (the Link will be UNIDIRECTIONAL). 
                    Is not present in more complex cases.";
            }
            uses Tapi:Resource;
            description "The Link object class models effective adjacency between two or more ForwardingDomains (FD). ";
        }
        grouping Node {
            list _ownedNodeEdgePoint {
                key 'uuid';
                config false;
                uses NodeEdgePoint;
                description "none";
            }
            leaf-list _aggregatedNodeEdgePoint {
                type leafref {
                    path '/Tapi:Context/Tapi:_topology/_node/_ownedNodeEdgePoint/uuid';
                }
                config false;
                description "none";
            }
            leaf _encapTopology {
                type leafref {
                    path '/Tapi:Context/Tapi:_topology/Tapi:uuid';
                }
                config false;
                description "none";
            }
            container _state {
                config false;
                uses Tapi:AdminStatePac;
                description "none";
            }
            container _transferCapacity {
                config false;
                uses TransferCapacityPac;
                description "none";
            }
            container _transferCost {
                config false;
                uses TransferCostPac;
                description "none";
            }
            container _transferIntegrity {
                config false;
                uses TransferIntegrityPac;
                description "none";
            }
            container _transferTiming {
                config false;
                uses TransferTimingPac;
                description "none";
            }
            leaf-list layerProtocolName {
                type Tapi:LayerProtocolName;
                config false;
                min-elements 1;
                description "none";
            }
            uses Tapi:Resource;
            description "The ForwardingDomain (FD) object class models the “ForwardingDomain” topological component which is used to effect forwarding of transport characteristic information and offers the potential to enable forwarding. 
                At the lowest level of recursion, an FD (within a network element (NE)) represents a switch matrix (i.e., a fabric). Note that an NE can encompass multiple switch matrices (FDs). ";
        }
        grouping Topology {
            list _node {
                key 'uuid';
                config false;
                uses Node;
                description "none";
            }
            list _link {
                key 'uuid';
                config false;
                uses Link;
                description "none";
            }
            leaf-list layerProtocolName {
                type Tapi:LayerProtocolName;
                config false;
                description "none";
            }
            uses Tapi:Resource;
            description "The ForwardingDomain (FD) object class models the “ForwardingDomain” topological component which is used to effect forwarding of transport characteristic information and offers the potential to enable forwarding. 
                At the lowest level of recursion, an FD (within a network element (NE)) represents a switch matrix (i.e., a fabric). Note that an NE can encompass multiple switch matrices (FDs). ";
        }
        grouping LayerProtocolTransitionPac {
            leaf-list transitionedLayerProtocolName {
                type string;
                min-elements 1;
                description "Provides the ordered structure of layer protocol transitions encapsulated in the TopologicalEntity. The ordering relates to the LinkPort role.";
            }
            leaf-list _nodeEdgePoint {
                type leafref {
                    path '/Tapi:Context/Tapi:_topology/_node/_ownedNodeEdgePoint/uuid';
                }
                min-elements 1;
                description "Lists the LTPs that define the layer protocol transition of the transitional link.";
            }
            description "Relevant for a Link that is formed by abstracting one or more LTPs (in a stack) to focus on the flow and deemphasize the protocol transformation. 
                This abstraction is relevant when considering multi-layer routing. 
                The layer protocols of the LTP and the order of their application to the signal is still relevant and need to be accounted for. This is derived from the LTP spec details.
                This Pac provides the relevant abstractions of the LTPs and provides the necessary association to the LTPs involved.
                Links that included details in this Pac are often referred to as Transitional Links.";
        }
        grouping LinkPort {
            leaf _nodeEdgePoint {
                type leafref {
                    path '/Tapi:Context/Tapi:_topology/_node/_ownedNodeEdgePoint/uuid';
                }
                config false;
                description "none";
            }
            leaf role {
                type Tapi:PortRole;
                config false;
                description "Each LinkEnd of the Link has a role (e.g., symmetric, hub, spoke, leaf, root)  in the context of the Link with respect to the Link function. ";
            }
            leaf direction {
                type Tapi:PortDirection;
                config false;
                description "The orientation of defined flow at the LinkEnd.";
            }
            uses Tapi:LocalClass;
            description "The association of the Link to LTPs is made via LinkEnd.
                The LinkEnd object class models the access to the Link function. 
                The traffic forwarding between the associated LinkEnds of the Link depends upon the type of Link.  
                In cases where there is resilience the LinkEnd may convey the resilience role of the access to the Link. 
                The Link can be considered as a component and the LinkEnd as a Port on that component";
        }
        grouping NodeEdgePoint {
            list _layerProtocol {
                key 'localId';
                config false;
                min-elements 1;
                uses Tapi:LayerProtocol;
                description "none";
            }
            leaf-list _clientNodeEdgePoint {
                type leafref {
                    path '/Tapi:Context/Tapi:_topology/_node/_ownedNodeEdgePoint/uuid';
                }
                config false;
                description "none";
            }
            container _state {
                config false;
                uses Tapi:AdminStatePac;
                description "none";
            }
            leaf direction {
                type Tapi:TerminationDirection;
                config false;
                description "none";
            }
            uses Tapi:Resource;
            description "The LogicalTerminationPoint (LTP) object class encapsulates the termination and adaptation functions of one or more transport layers. 
                The structure of LTP supports all transport protocols including circuit and packet forms.";
        }
        grouping RiskParameterPac {
            list riskCharacteristic {
                key 'riskCharacteristicName';
                config false;
                min-elements 1;
                uses RiskCharacteristic;
                description "A list of risk characteristics for consideration in an analysis of shared risk. Each element of the list represents a specific risk consideration.";
            }
            description "The risk characteristics of a TopologicalEntity come directly from the underlying physical realization. 
                The risk characteristics propagate from the physical realization to the client and from the server layer to the client layer, this propagation may be modified by protection.
                A TopologicalEntity may suffer degradation or failure as a result of a problem in a part of the underlying realization.
                The realization can be partitioned into segments which have some relevant common failure modes.
                There is a risk of failure/degradation of each segment of the underlying realization.
                Each segment is a part of a larger physical/geographical unit that behaves as one with respect to failure (i.e. a failure will have a high probability of impacting the whole unit (e.g. all cables in the same duct).
                Disruptions to that larger physical/geographical unit will impact (cause failure/errors to) all TopologicalEntities that use any part of that larger physical/geographical entity.
                Any TopologicalEntity that uses any part of that larger physical/geographical unit will suffer impact and hence each TopologicalEntity shares risk.
                The identifier of each physical/geographical unit that is involved in the realization of each segment of a Topological entity can be listed in the RiskParameter_Pac of that TopologicalEntity.
                A segment has one or more risk characteristic.
                Shared risk between two TopologicalEntities compromises the integrity of any solution that use one of those TopologicalEntity as a backup for the other.
                Where two TopologicalEntities have a common risk characteristic they have an elevated probability of failing simultaneously compared to two TopologicalEntities that do not share risk characteristics.";
        }
        grouping TransferCapacityPac {
            container totalPotentialCapacity {
                config false;
                uses Capacity;
                description "An optimistic view of the capacity of the TopologicalEntity assuming that any shared capacity is available to be taken.";
            }
            container availableCapacity {
                config false;
                uses Capacity;
                description "Capacity available to be assigned.";
            }
            list capacityAssignedToUserView {
                key 'numberingRange';
                config false;
                uses Capacity;
                description "Capacity already assigned";
            }
            leaf capacityInteractionAlgorithm {
                type string;
                config false;
                description "A reference to an algorithm that describes how various chunks of allocated capacity interact (e.g. when shared)";
            }
            description "The TopologicalEntity derives capacity from the underlying realization. 
                A TopologicalEntity may be an abstraction and virtualization of a subset of the underlying capability offered in a view or may be directly reflecting the underlying realization.
                A TopologicalEntity may be directly used in the view or may be assigned to another view for use.
                The clients supported by a multi-layer TopologicalEntity may interact such that the resources used by one client may impact those available to another. This is derived from the LTP spec details.
                Represents the capacity available to user (client) along with client interaction and usage. 
                A TopologicalEntity may reflect one or more client protocols and one or more members for each profile.";
        }
        grouping TransferCostPac {
            list costCharacteristic {
                key 'costAlgorithm';
                config false;
                min-elements 1;
                uses CostCharacteristic;
                description "The list of costs where each cost relates to some aspect of the TopologicalEntity.";
            }
            description "The cost characteristics of a TopologicalEntity not necessarily correlated to the cost of the underlying physical realization. 
                They may be quite specific to the individual TopologicalEntity e.g. opportunity cost. Relates to layer capacity
                There may be many perspectives from which cost may be considered  for a particular TopologicalEntity and hence many specific costs and potentially cost algorithms. 
                Using an entity will incur a cost. ";
        }
        grouping TransferIntegrityPac {
            leaf errorCharacteristic {
                type string;
                config false;
                description "Describes the degree to which the signal propagated can be errored. 
                    Applies to TDM systems as the errored signal will be propagated and not packet as errored packets will be discarded.";
            }
            leaf lossCharacteristic {
                type string;
                config false;
                description "Describes the acceptable characteristic of lost packets where loss may result from discard due to errors or overflow.
                    Applies to packet systems and not TDM (as for TDM errored signals are propagated unless grossly errored and overflow/underflow turns into timing slips).";
            }
            leaf repeatDeliveryCharacteristic {
                type string;
                config false;
                description "Primarily applies to packet systems where a packet may be delivered more than once (in fault recovery for example). 
                    It can also apply to TDM where several frames may be received twice due to switching in a system with a large differential propagation delay.";
            }
            leaf deliveryOrderCharacteristic {
                type string;
                config false;
                description "Describes the degree to which packets will be delivered out of sequence.
                    Does not apply to TDM as the TDM protocols maintain strict order.";
            }
            leaf unavailableTimeCharacteristic {
                type string;
                config false;
                description "Describes the duration for which there may be no valid signal propagated.";
            }
            leaf serverIntegrityProcessCharacteristic {
                type string;
                config false;
                description "Describes the effect of any server integrity enhancement process on the characteristics of the TopologicalEntity.";
            }
            description "Transfer intergrity characteristic covers expected/specified/acceptable characteristic of degradation of the transfered signal.
                It includes all aspects of possible degradation of signal content as well as any damage of any form to the total TopologicalEntity and to the carried signals.
                Note that the statement is of total impact to the TopologicalEntity so any partial usage of the TopologicalEntity (e.g. a signal that does not use full capacity) will only suffer its portion of the impact.";
        }
        grouping TransferTimingPac {
            leaf fixedLatencyCharacteristic {
                type string;
                config false;
                description "A TopologicalEntity suffers delay caused by the realization of the servers (e.g. distance related; FEC encoding etc.) along with some client specific processing. This is the total average latency effect of the TopologicalEntity";
            }
            leaf jitterCharacteristic {
                type string;
                config false;
                description "High frequency deviation from true periodicity of a signal and therefore a small high rate of change of transfer latency.
                    Applies to TDM systems (and not packet).";
            }
            leaf wanderCharacteristic {
                type string;
                config false;
                description "Low frequency deviation from true periodicity of a signal and therefore a small low rate of change of transfer latency.
                    Applies to TDM systems (and not packet).";
            }
            list queuingLatency {
                key 'latencyValue';
                config false;
                uses QueuingLatency;
                description "The effect on the latency of a queuing process. This only has significant effect for packet based systems and has a complex characteristic.";
            }
            description "A TopologicalEntity will suffer effects from the underlying physical realization related to the timing of the information passed by the TopologicalEntity.";
        }
        grouping ValidationPac {
            list validationMechanism {
                key 'validationRobustness';
                config false;
                min-elements 1;
                uses ValidationMechanism;
                description "Provides details of the specific validation mechanism(s) used to confirm the presence of an intended topologicalEntity.";
            }
            description "Validation covers the various adjacenct discovery and reachability verification protocols. Also may cover Information source and degree of integrity.";
        }
        grouping TeLink {
            leaf-list _node {
                type leafref {
                    path '/Tapi:Context/Tapi:_topology/_node/uuid';
                }
                config false;
                min-elements 2;
                max-elements 2;
                description "none";
            }
            leaf-list _nodeEdgePoint {
                type leafref {
                    path '/Tapi:Context/Tapi:_topology/_node/_ownedNodeEdgePoint/uuid';
                }
                config false;
                max-elements 2;
                description "none";
            }
            uses Tapi:LocalClass;
            description "The Link object class models effective adjacency between two or more ForwardingDomains (FD). ";
        }
    
    /***********************
    * package TypeDefinitions
    **********************/ 
        grouping Capacity {
            leaf totalSize {
                type string;
                description "Total capacity of the TopologicalEntity in MB/s";
            }
            leaf maximumUsageInstances {
                type string;
                description "Where there is some limit to the number of client (e.g. in a channelized case).";
            }
            leaf maximumUsageSize {
                type string;
                description "Where a client is of variable capacity but due to some underlying realization the maximum size of the client is smaller than the totalSize.";
            }
            leaf numberingRange {
                type string;
                description "Method for identifying units of capacity via some numbering scheme.";
            }
            description "Information on capacity of a particular TopologicalEntity.";
        }
        grouping CostCharacteristic {
            leaf costName {
                type string;
                description "The cost characteristic will related to some aspect of the TopologicalEntity (e.g. $ cost, routing weight). This aspect will be conveyed by the costName.";
            }
            leaf costValue {
                type string;
                description "The specific cost.";
            }
            leaf costAlgorithm {
                type string;
                description "The cost may vary based upon some properties of the TopologicalEntity. The rules for the variation are conveyed by the costAlgorithm.";
            }
            description "The information for a particular cost characteristic.";
        }
        typedef FixedCapacityValue {
            type enumeration {
                enum NOT_APPLICABLE {
                    description "none";
                }
                enum 10MBPS {
                    description "none";
                }
                enum 100MBPS {
                    description "none";
                }
                enum 1GBPS {
                    description "none";
                }
                enum 2.4GBPS {
                    description "none";
                }
                enum 10GBPS {
                    description "none";
                }
                enum 40GBPS {
                    description "none";
                }
                enum 100GBPS {
                    description "none";
                }
                enum 200GBPS {
                    description "none";
                }
                enum 400GBPS {
                    description "none";
                }
            }
            description "The Capacity (Bandwidth) values that are applicable for digital layers. ";
        }
        grouping QueuingLatency {
            leaf trafficPropertyName {
                type string;
                description "The identifier of the specific traffic property to which the queuing latency applies.";
            }
            leaf latencyValue {
                type string;
                description "The specific queuing latency for the traffic property.";
            }
            description "Provides information on latency characteristic for a particular stated trafficProperty.";
        }
        grouping RiskCharacteristic {
            leaf riskCharacteristicName {
                type string;
                description "The name of the risk characteristic. The characteristic may be related to a specific degree of closeness. 
                    For example a particular characteristic may apply to failures that are localized (e.g. to one side of a road) where as another characteristic may relate to failures that have a broader impact (e.g. both sides of a road that crosses a bridge).
                    Depending upon the importance of the traffic being routed different risk characteristics will be evaluated.";
            }
            leaf-list riskIdentifierList {
                type string;
                min-elements 1;
                description "A list of the identifiers of each physical/geographic unit (with the specific risk characteristic) that is related to a segment of the TopologicalEntity.";
            }
            description "The information for a particular risk characteristic where there is a list of risk identifiers related to that characteristic.";
        }
        grouping ValidationMechanism {
            leaf validationMechanism {
                type string;
                description "Name of mechanism used to validate adjacency";
            }
            leaf layerProtocolAdjacencyValidated {
                type string;
                description "State of validatiion";
            }
            leaf validationRobustness {
                type string;
                description "Quality of validation (i.e. how likely is the stated validation to be invalid)";
            }
            description "Identifies the validation mechanism and describes the characteristics of that mechanism";
        }
    
    /***********************
    * package Interfaces
    **********************/ 
        rpc getTopologyDetails {
            description "none";
            input {
                leaf topologyIdOrName {
                    type string;
                    description "none";
                }
            }
            output {
                container topology {
                    uses Topology;
                    description "none";
                }
            }
        }
        rpc getNodeDetails {
            description "none";
            input {
                leaf topologyIdOrName {
                    type string;
                    description "none";
                }
                leaf nodeIdOrName {
                    type string;
                    description "none";
                }
            }
            output {
                container node {
                    uses Node;
                    description "none";
                }
            }
        }
        rpc getNodeEdgePointDetails {
            description "none";
            input {
                leaf topologyIdOrName {
                    type string;
                    description "none";
                }
                leaf nodeIdOrName {
                    type string;
                    description "none";
                }
                leaf epIdOrName {
                    type string;
                    description "none";
                }
            }
            output {
                container nodeEdgePoint {
                    uses NodeEdgePoint;
                    description "none";
                }
            }
        }
        rpc getLinkDetails {
            description "none";
            input {
                leaf topologyIdOrName {
                    type string;
                    description "none";
                }
                leaf linkIdOrName {
                    type string;
                    description "none";
                }
            }
            output {
                container link {
                    uses Link;
                    description "none";
                }
            }
        }
        rpc getTopologyList {
            description "none";
            output {
                list topology {
                    uses Topology;
                    description "none";
                }
            }
        }
    
}
