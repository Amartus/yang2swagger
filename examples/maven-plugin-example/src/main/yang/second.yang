module pingpong-module {
  namespace "http://amartus/ns/yang/pingpong-module";
  prefix s;
  organization "test-yang";
  description "example-module to demo maven integration";

  revision 2016-08-08 {
      description "Final";
  }

  container configuration {
    leaf customize {
        type boolean;
    }
    container test {
        leaf test {
            type string;
        }
    }
  }

  rpc ping {
    input {
      leaf ping {
          type string;
      }
    }
      output {
          container response {
              leaf pong {
                  type string;
              }
          }
      }
    }
}
